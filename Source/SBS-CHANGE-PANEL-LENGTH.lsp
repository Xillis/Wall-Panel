(defun C:SBS-CHANGE-PANEL-LENGTH ( / OBJ PANELS INDEX VALUE MODE)
	(vl-load-com)
	(setq
		PANELS(ssget )
		INDEX 0
		VALUE (abs (getdist "Enter length: "))
	)
	(initget 1 "A S Add Subtract")
	(setq MODE (strcase (getkword "Add or Subtract? ")))
	(if (or (= "S" MODE) (= "SUBTRACT" MODE))
		(setq VALUE (- (abs VALUE)))
	)
	(while (/= NIL(setq OBJ (ssname PANELS INDEX)))
		(vl-some
			'(lambda ( x )
				(if (= "PANEL LENGTH" (strcase (vla-get-propertyname x)))
					(vla-put-value x (vlax-make-variant (+ (vlax-variant-value(vla-get-value x)) VALUE ) (vlax-variant-type (vla-get-value x))))
				)
			)
			(vlax-invoke (VLAX-ENAME->VLA-OBJECT OBJ) 'getdynamicblockproperties)
		)
		(setq INDEX (1+ INDEX))		
	)
)
